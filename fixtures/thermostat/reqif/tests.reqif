# Plan de tests du thermostat

# Specification: Plan de tests du thermostat

## o-title: Plan de tests du thermostat

### o-s1: Tests unitaires

#### TST_REQ1: Période d'échantillonnage
Vérifier 6 lectures par minute.
- Satisfies -> DES_REQ1

#### TST_REQ2: Table d'étalonnage
Comparer 16 points à une sonde de référence.
- Satisfies -> DES_REQ2

#### TST_REQ3: Saturation
Envoyer 5 °C et 35 °C, vérifier 7 °C et 30 °C.
- Satisfies -> DES_REQ3

#### TST_REQ4: Seuils du relais
Balayer la température autour de la consigne.
- Satisfies -> DES_REQ4

### o-s2: Tests d'intégration

#### TST_REQ5: API REST
Lire puis écrire la consigne par l'API.
- Satisfies -> DES_REQ5

#### TST_REQ6: Chien de garde
Bloquer la boucle principale, vérifier le redémarrage.
- Satisfies -> DES_REQ6

## DES_REQ1

## DES_REQ2

## DES_REQ3

## DES_REQ4

## DES_REQ5

## DES_REQ6
