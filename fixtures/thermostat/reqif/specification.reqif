# Spécification du thermostat

# Specification: Spécification du thermostat

## o-title: Spécification du thermostat

### o-s1: Mesure

#### THS_REQ1: Mesure de la température
Le thermostat doit mesurer la température ambiante toutes les 10 secondes.
- Priority: High

#### THS_REQ2: Précision de mesure
La précision de mesure doit être meilleure que 0,5 °C entre 5 °C et 35 °C.
- Priority: High

### o-s2: Régulation

#### THS_REQ3: Consigne
L'utilisateur doit pouvoir régler une consigne entre 7 °C et 30 °C.
- Priority: Medium

#### THS_REQ4: Hystérésis
Le chauffage doit être commandé avec une hystérésis de 0,3 °C.
- Priority: Medium

#### THS_REQ5: Mode absence
Un mode absence doit abaisser la consigne de 3 °C.
- Priority: Low

### o-s3: Connectivité

#### THS_REQ6: Pilotage à distance
La consigne doit pouvoir être modifiée depuis une application mobile.
- Priority: Low
