# Conception du thermostat

# Specification: Conception du thermostat

## o-title: Conception du thermostat

### o-s1: Acquisition

#### DES_REQ1: Échantillonnage du capteur
Le capteur est lu par interruption toutes les 10 s.
- Satisfies -> THS_REQ1

#### DES_REQ2: Étalonnage
Une table d'étalonnage en 16 points corrige la non-linéarité du capteur.
- Satisfies -> THS_REQ2

### o-s2: Régulateur

#### DES_REQ3: Bornes de consigne
La consigne est saturée entre 7 °C et 30 °C.
- Satisfies -> THS_REQ3

#### DES_REQ4: Commande tout-ou-rien
Le relais est commandé avec un seuil haut et un seuil bas.
- Satisfies -> THS_REQ4

#### DES_REQ5: API de consigne
Une API REST expose la lecture et l'écriture de la consigne.
- Satisfies -> THS_REQ6
- Satisfies -> THS_REQ99

### o-s3: Exigences dérivées

#### DES_REQ6: Chien de garde
Un chien de garde redémarre le microcontrôleur après 2 s sans activité.

#### DES_REQ7: Journal d'erreurs
Les 100 dernières erreurs sont conservées en mémoire non volatile.

## THS_REQ1

## THS_REQ2

## THS_REQ3

## THS_REQ4

## THS_REQ6

## THS_REQ99
